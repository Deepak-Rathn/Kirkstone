--
-- PE-HSD-CPE-MIB.mib
-- MIB generated by MG-SOFT Visual MIB Builder 2013 (64-bit) Version 9.0  Build 760
-- Thursday, October 22, 2015 at 14:36:55
--

--  File Name : PE-HSD-CPE-MIB

	PE-HSD-CPE-MIB DEFINITIONS ::= BEGIN
 
		IMPORTS
			comcast			
				FROM COMCAST-SMI			
			OBJECT-GROUP			
				FROM SNMPv2-CONF			
			Integer32, Unsigned32, OBJECT-TYPE, MODULE-IDENTITY			
				FROM SNMPv2-SMI			
			TruthValue, DisplayString , RowStatus			
				FROM SNMPv2-TC;
	
	
		-- 1.3.6.1.4.1.17270.44
		peHSDCPE MODULE-IDENTITY 
			LAST-UPDATED "201510221435Z"		-- October 22, 2015 at 14:35 GMT
			ORGANIZATION 
				"Comcast Cable"
			CONTACT-INFO 
				"Deven Vazirani
				Comcast Cable
				Email: deven_vazirani@cable.comcast.com"
			DESCRIPTION 
				"This is the MIB Module for HSD features - Self-Heal, Dynamic Channel Selection (DCS), 
				Air Time Management (ATM)"
			REVISION "201510221435Z"		-- October 22, 2015 at 14:35 GMT
			DESCRIPTION 
				"Ver 0.3 Updates for DCS feature"
			REVISION "201509041050Z"		-- September 04, 2015 at 10:50 GMT
			DESCRIPTION 
				"Ver 0.2 Incorporated review feedback"
			REVISION "201506091342Z"		-- June 09, 2015 at 13:42 GMT
			DESCRIPTION 
				"Ver 0.1 Initial revision"
			::= { comcast 44 }

		
	
	
--
-- Node definitions
--
	
		-- 1.3.6.1.4.1.17270.44.1
		peHSDCPEMIBObjects OBJECT IDENTIFIER ::= { peHSDCPE 1 }

		
-- Self-Heal feature objects
		-- 1.3.6.1.4.1.17270.44.1.1
		selfHeal OBJECT IDENTIFIER ::= { peHSDCPEMIBObjects 1 }

		
		-- 1.3.6.1.4.1.17270.44.1.1.1
		enableSelfHeal OBJECT-TYPE
			SYNTAX TruthValue
			MAX-ACCESS read-write
			STATUS current
			DESCRIPTION
				"Flag to enable/disable Self Heal feature on the device. By default this value is false 
				and the feature is disabled."
			::= { selfHeal 1 }

		
		-- 1.3.6.1.4.1.17270.44.1.1.2
		numPingsPerServer OBJECT-TYPE
			SYNTAX Unsigned32
			MAX-ACCESS read-write
			STATUS current
			DESCRIPTION
				"Number of pings per servers to ping while testing connectivity. Default value is 3."
			::= { selfHeal 2 }

		
		-- 1.3.6.1.4.1.17270.44.1.1.3
		minNumPingServer OBJECT-TYPE
			SYNTAX Unsigned32
			MAX-ACCESS read-write
			STATUS current
			DESCRIPTION
				"Minimum number of servers (of each kind - IPv4 and IPv6) to ping while testing 
				connectivity. Should be less than or equal to number of servers in the ping server table.
				Default value is 1."
			::= { selfHeal 3 }

		
		-- 1.3.6.1.4.1.17270.44.1.1.4
		pingInterval OBJECT-TYPE
			SYNTAX Unsigned32 (15..1440)
			MAX-ACCESS read-write
			STATUS current
			DESCRIPTION
				"Interval of time, in minutes, between testing connectivity to a server. Each 
				connectivity test comprises of 1 or more pings (as specified in numPingsPerServer) to the server
				Minimum ping interval: 15 mins
				Maximum ping interval: 1440 mins (24 hours)
				Default: 60 mins"
			::= { selfHeal 4 }

		
		-- 1.3.6.1.4.1.17270.44.1.1.5
		pingRespWaitTime OBJECT-TYPE
			SYNTAX Unsigned32 (1..1000)
			MAX-ACCESS read-write
			STATUS current
			DESCRIPTION
				"ICMP (ping) echo reply wait time (in milliseconds) to validate success or failure of 
				a ping test."
			::= { selfHeal 5 }

		
-- List of ping servers
		-- 1.3.6.1.4.1.17270.44.1.1.6
		pingServerList OBJECT IDENTIFIER ::= { selfHeal 6 }

		
		-- 1.3.6.1.4.1.17270.44.1.1.6.1
		ipv4PingServerTable OBJECT-TYPE
			SYNTAX SEQUENCE OF Ipv4PingServerEntry
			MAX-ACCESS not-accessible
			STATUS current
			DESCRIPTION
				"Table containing the list of IPv4 ping servers"
			::= { pingServerList 1 }

		
		-- 1.3.6.1.4.1.17270.44.1.1.6.1.1
		ipv4PingServerEntry OBJECT-TYPE
			SYNTAX Ipv4PingServerEntry
			MAX-ACCESS not-accessible
			STATUS current
			DESCRIPTION
				"IPv4 ping server row entry"
			INDEX { ipv4PingServerIndex }
			::= { ipv4PingServerTable 1 }

		
		Ipv4PingServerEntry ::=
			SEQUENCE { 
				ipv4PingServerIndex Unsigned32,
				ipv4PingServerURI DisplayString,
				ipv4PingServerRowStatus        RowStatus
			 }

		-- 1.3.6.1.4.1.17270.44.1.1.6.1.1.1
		ipv4PingServerIndex OBJECT-TYPE
			SYNTAX Unsigned32 (1..4294967295)
			MAX-ACCESS not-accessible
			STATUS current
			DESCRIPTION
				"Row entry index for the ping server table"
			::= { ipv4PingServerEntry 1 }

		
		-- 1.3.6.1.4.1.17270.44.1.1.6.1.1.2
		ipv4PingServerURI OBJECT-TYPE
			SYNTAX DisplayString
			MAX-ACCESS read-write
			STATUS current
			DESCRIPTION
				"URI for the ping server to be pinged. Should resolve to an IPv4 address."
			::= { ipv4PingServerEntry 2 }
			
		ipv4PingServerRowStatus OBJECT-TYPE
            SYNTAX      RowStatus
            MAX-ACCESS  read-write
            STATUS      current
            DESCRIPTION
                "The row status. A row can be destroyed.
                 If the row is not used, set to notInService."
            ::= { ipv4PingServerEntry 3 }	

		
		-- 1.3.6.1.4.1.17270.44.1.1.6.2
		ipv6PingServerTable OBJECT-TYPE
			SYNTAX SEQUENCE OF Ipv6PingServerEntry
			MAX-ACCESS not-accessible
			STATUS current
			DESCRIPTION
				"Table containing the list of IPv6 ping servers"
			::= { pingServerList 2 }

		
		-- 1.3.6.1.4.1.17270.44.1.1.6.2.1
		ipv6PingServerEntry OBJECT-TYPE
			SYNTAX Ipv6PingServerEntry
			MAX-ACCESS not-accessible
			STATUS current
			DESCRIPTION
				"IPv6 ping server row entry"
			INDEX { ipv6PingServerIndex }
			::= { ipv6PingServerTable 1 }

		
		Ipv6PingServerEntry ::=
			SEQUENCE { 
				ipv6PingServerIndex Unsigned32,
				ipv6PingServerURI DisplayString,
				ipv6PingServerRowStatus    RowStatus
			 }

		-- 1.3.6.1.4.1.17270.44.1.1.6.2.1.1
		ipv6PingServerIndex OBJECT-TYPE
			SYNTAX Unsigned32 (1..4294967295)
			MAX-ACCESS not-accessible
			STATUS current
			DESCRIPTION
				"Row entry index for the ping server table"
			::= { ipv6PingServerEntry 1 }

		
		-- 1.3.6.1.4.1.17270.44.1.1.6.2.1.2
		ipv6PingServerURI OBJECT-TYPE
			SYNTAX DisplayString
			MAX-ACCESS read-write
			STATUS current
			DESCRIPTION
				"URI for the ping server to be pinged. Should resolve to an IPv6 address."
			::= { ipv6PingServerEntry 2 }

        ipv6PingServerRowStatus OBJECT-TYPE
            SYNTAX      RowStatus
            MAX-ACCESS  read-write
            STATUS      current
            DESCRIPTION
                "The row status. A row can be destroyed.
                 If the row is not used, set to notInService."
            ::= { ipv6PingServerEntry 3 }
		
		-- 1.3.6.1.4.1.17270.44.1.1.7
		resourceUsageComputeWindow OBJECT-TYPE
			SYNTAX Unsigned32
			MAX-ACCESS read-write
			STATUS current
			DESCRIPTION
				"Window of time (in minutes) over which the average resource usage is to be computed. 
				Default time window is 15 minutes."
			::= { selfHeal 7 }

		
		-- 1.3.6.1.4.1.17270.44.1.1.8
		avgCPUThreshold OBJECT-TYPE
			SYNTAX Unsigned32 (0..100)
			MAX-ACCESS read-write
			STATUS current
			DESCRIPTION
				"Average CPU usage threshold percentage above which corrective action is to be required.
				Default value is 100%"
			::= { selfHeal 8 }

		
		-- 1.3.6.1.4.1.17270.44.1.1.9
		avgMemoryThreshold OBJECT-TYPE
			SYNTAX Unsigned32 (0..100)
			MAX-ACCESS read-write
			STATUS current
			DESCRIPTION
				"Average memory usage threshold percentage above which corrective action is to be required.
				Default value is 100%"
			::= { selfHeal 9 }

		
		-- 1.3.6.1.4.1.17270.44.1.1.10
		maxRebootCount OBJECT-TYPE
			SYNTAX Unsigned32 (0..24)
			MAX-ACCESS read-write
			STATUS current
			DESCRIPTION
				"Maximum number of watchdog initiated reboots per 24 hour period from initial power up.
				Default value is 3 reboots in a 24 hour period."
			::= { selfHeal 10 }

		
		-- 1.3.6.1.4.1.17270.44.1.1.11
		maxSubsystemResetCount OBJECT-TYPE
			SYNTAX Unsigned32
			MAX-ACCESS read-write
			STATUS current
			DESCRIPTION
				"Maximum number of resets per 24 hour period from initial power up.
				Default value is 5 resets in a 24 hour period."
			::= { selfHeal 11 }
			
		-- 1.3.6.1.4.1.17270.44.1.1.12
		diagMode OBJECT-TYPE
			SYNTAX TruthValue
			MAX-ACCESS read-write
			STATUS current
			DESCRIPTION
				"Flag to enable/disable diagnostistic mode for Self Heal. In diagnostic mode, the 
				device detects connection failures, resource usage threshold being exceeded but
				does not take corrective action. By default this value is false and the device 
				will take corrective action."
			::= { selfHeal 12 }

		
		-- 1.3.6.1.4.1.17270.44.1.1.13
		diagModeLogUploadFrequency OBJECT-TYPE
			SYNTAX Unsigned32
			MAX-ACCESS read-write
			STATUS current
			DESCRIPTION
				"Frequency (in minutes) at which resource monitoring and connection error logs to be uploaded
				Default log upload rate is once every 1440 minutes (24 hours)."
			::= { selfHeal 13 }
		
-- IpPing Selection feature objects
		-- 1.3.6.1.4.1.17270.44.1.2
		IPPing OBJECT IDENTIFIER ::= { peHSDCPEMIBObjects 2 }

		
		-- 1.3.6.1.4.1.17270.44.1.2.1
		DataBlockSize OBJECT-TYPE
			SYNTAX Unsigned32 
			MAX-ACCESS read-write
			STATUS current
			DESCRIPTION
				" DataBlockSize represents size of the data block in bytes to be sent for each ping"
			::= { IPPing 1 }

		
-- Channel pools
		-- 1.3.6.1.4.1.17270.44.1.2.2
		channelPool OBJECT IDENTIFIER ::= { dcs 2 }

		
		-- 1.3.6.1.4.1.17270.44.1.2.2.1
		channelPool24GTable OBJECT-TYPE
			SYNTAX SEQUENCE OF ChannelPool24GEntry
			MAX-ACCESS not-accessible
			STATUS current
			DESCRIPTION
				"Table containing the list of 2.4GHz channels"
			::= { channelPool 1 }

		
		-- 1.3.6.1.4.1.17270.44.1.2.2.1.1
		channelPool24GEntry OBJECT-TYPE
			SYNTAX ChannelPool24GEntry
			MAX-ACCESS not-accessible
			STATUS current
			DESCRIPTION
				"2.4GHz channel row entry"
			INDEX { channelPool24GIndex }
			::= { channelPool24GTable 1 }

		
		ChannelPool24GEntry ::=
			SEQUENCE { 
				channelPool24GIndex
					Unsigned32,
				channelNum24G
					Integer32
			 }

		-- 1.3.6.1.4.1.17270.44.1.2.2.1.1.1
		channelPool24GIndex OBJECT-TYPE
			SYNTAX Unsigned32 (1..11)
			MAX-ACCESS not-accessible
			STATUS current
			DESCRIPTION
				"Row entry index for the 2.4GHz channel pool"
			::= { channelPool24GEntry 1 }

		
		-- 1.3.6.1.4.1.17270.44.1.2.2.1.1.2
		channelNum24G OBJECT-TYPE
			SYNTAX Integer32 (1..11)
			MAX-ACCESS read-only
			STATUS current
			DESCRIPTION
				"2.4GHz channel number for scoring."
			::= { channelPool24GEntry 2 }

		
		-- 1.3.6.1.4.1.17270.44.1.2.2.2
		channelPool5GTable OBJECT-TYPE
			SYNTAX SEQUENCE OF ChannelPool5GEntry
			MAX-ACCESS not-accessible
			STATUS current
			DESCRIPTION
				"Table containing the list of IPv6 ping servers"
			::= { channelPool 2 }

		
		-- 1.3.6.1.4.1.17270.44.1.2.2.2.1
		channelPool5GEntry OBJECT-TYPE
			SYNTAX ChannelPool5GEntry
			MAX-ACCESS not-accessible
			STATUS current
			DESCRIPTION
				"IPv6 ping server row entry"
			INDEX { channelPool5GIndex }
			::= { channelPool5GTable 1 }

		
		ChannelPool5GEntry ::=
			SEQUENCE { 
				channelPool5GIndex
					Unsigned32,
				channelNum5G
					Unsigned32
			 }

		-- 1.3.6.1.4.1.17270.44.1.2.2.2.1.1
		channelPool5GIndex OBJECT-TYPE
			SYNTAX Unsigned32 (1..130)
			MAX-ACCESS not-accessible
			STATUS current
			DESCRIPTION
				"Row entry index for the 5GHz channel pool"
			::= { channelPool5GEntry 1 }

		
		-- 1.3.6.1.4.1.17270.44.1.2.2.2.1.2
		channelNum5G OBJECT-TYPE
			SYNTAX Unsigned32 (36..165)
			MAX-ACCESS read-only
			STATUS current
			DESCRIPTION
				"5 GHz channel number for scoring."
			::= { channelPool5GEntry 2 }

		
		-- 1.3.6.1.4.1.17270.44.1.2.3
		preferred5GChanBw OBJECT-TYPE
			SYNTAX Unsigned32 (20..80)
			MAX-ACCESS read-write
			STATUS current
			DESCRIPTION
				"Preferred channel bandwidth for the 5G channels to use. Default 20 MHz wide."
			::= { dcs 3 }

		
		-- 1.3.6.1.4.1.17270.44.1.2.4
		scanDwellTime OBJECT-TYPE
			SYNTAX Unsigned32 (30..50)
			MAX-ACCESS read-write
			STATUS current
			DESCRIPTION
				"Time in milliseconds to dwell on a channel for scoring purposes. Range from 30 - 50 ms. 
				Default value 40 ms"
			::= { dcs 4 }

		
		-- 1.3.6.1.4.1.17270.44.1.2.5
		maxScanSamples OBJECT-TYPE
			SYNTAX Unsigned32 (48..144)
			MAX-ACCESS read-write
			STATUS current
			DESCRIPTION
				"Maximum scan samples per 24 hour period. Minimum samples 48 (1 sample every 30 minutes).
				Maximum samples 144 (1 sample every 10 minutes). Default value 48 samples"
			::= { dcs 5 }

		
		-- 1.3.6.1.4.1.17270.44.1.2.6
		chanScoreEvalMinInterval OBJECT-TYPE
			SYNTAX Unsigned32
			MAX-ACCESS read-write
			STATUS current
			DESCRIPTION
				"Channel score minimum evaluation interval. Period (in hours) after which channel 
				scores are to be evaluated. Default interval 24 hours"
			::= { dcs 6 }

		
		-- 1.3.6.1.4.1.17270.44.1.2.7
		chanScoreDiffThreshold OBJECT-TYPE
			SYNTAX Unsigned32
			MAX-ACCESS read-write
			STATUS current
			DESCRIPTION
				"Channel score differential threshold. Channel score difference threshold to be 
				surpassed in order to elicit a channel change. Default value is 1."
			::= { dcs 7 }

		
-- Channel scores
		-- 1.3.6.1.4.1.17270.44.1.2.8
		channelScores OBJECT IDENTIFIER ::= { dcs 8 }

		
		-- 1.3.6.1.4.1.17270.44.1.2.8.1
		channelScores24GTable OBJECT-TYPE
			SYNTAX SEQUENCE OF ChannelScores24GEntry
			MAX-ACCESS not-accessible
			STATUS current
			DESCRIPTION
				"Table containing the list of 2.4GHz channels"
			::= { channelScores 1 }

		
		-- 1.3.6.1.4.1.17270.44.1.2.8.1.1
		channelScores24GEntry OBJECT-TYPE
			SYNTAX ChannelScores24GEntry
			MAX-ACCESS not-accessible
			STATUS current
			DESCRIPTION
				"2.4GHz channel row entry"
			INDEX { channelScore24GIndex }
			::= { channelScores24GTable 1 }

		
		ChannelScores24GEntry ::=
			SEQUENCE { 
				channelScore24GIndex
					Unsigned32,
				channelScore24G
					Integer32
			 }

		-- 1.3.6.1.4.1.17270.44.1.2.8.1.1.1
		channelScore24GIndex OBJECT-TYPE
			SYNTAX Unsigned32 (1..11)
			MAX-ACCESS not-accessible
			STATUS current
			DESCRIPTION
				"Row entry index for the 2.4GHz channel pool"
			::= { channelScores24GEntry 1 }

		
		-- 1.3.6.1.4.1.17270.44.1.2.8.1.1.2
		channelScore24G OBJECT-TYPE
			SYNTAX Integer32
			MAX-ACCESS read-only
			STATUS current
			DESCRIPTION
				"2.4GHz channel number for scoring."
			::= { channelScores24GEntry 2 }

		
		-- 1.3.6.1.4.1.17270.44.1.2.8.2
		channelScores5GTable OBJECT-TYPE
			SYNTAX SEQUENCE OF ChannelScores5GEntry
			MAX-ACCESS not-accessible
			STATUS current
			DESCRIPTION
				"Table containing the list of IPv6 ping servers"
			::= { channelScores 2 }

		
		-- 1.3.6.1.4.1.17270.44.1.2.8.2.1
		channelScores5GEntry OBJECT-TYPE
			SYNTAX ChannelScores5GEntry
			MAX-ACCESS not-accessible
			STATUS current
			DESCRIPTION
				"IPv6 ping server row entry"
			INDEX { channelScore5GIndex }
			::= { channelScores5GTable 1 }

		
		ChannelScores5GEntry ::=
			SEQUENCE { 
				channelScore5GIndex
					Unsigned32,
				channelScore5G
					Unsigned32
			 }

		-- 1.3.6.1.4.1.17270.44.1.2.8.2.1.1
		channelScore5GIndex OBJECT-TYPE
			SYNTAX Unsigned32 (1..130)
			MAX-ACCESS not-accessible
			STATUS current
			DESCRIPTION
				"Row entry index for the 5GHz channel pool"
			::= { channelScores5GEntry 1 }

		
		-- 1.3.6.1.4.1.17270.44.1.2.8.2.1.2
		channelScore5G OBJECT-TYPE
			SYNTAX Unsigned32
			MAX-ACCESS read-only
			STATUS current
			DESCRIPTION
				"5 GHz channel number for scoring."
			::= { channelScores5GEntry 2 }

		
		-- 1.3.6.1.4.1.17270.44.1.2.9
		radioTrigEvTable OBJECT-TYPE
			SYNTAX SEQUENCE OF RadioTrigEvEntry
			MAX-ACCESS not-accessible
			STATUS current
			DESCRIPTION
				"Table containing the list of 2.4GHz channels"
			::= { dcs 9 }

		
		-- 1.3.6.1.4.1.17270.44.1.2.9.1
		radioTrigEvEntry OBJECT-TYPE
			SYNTAX RadioTrigEvEntry
			MAX-ACCESS not-accessible
			STATUS current
			DESCRIPTION
				"2.4GHz channel row entry"
			INDEX { radioIndex }
			::= { radioTrigEvTable 1 }

		
		RadioTrigEvEntry ::=
			SEQUENCE { 
				radioIndex
					Unsigned32,
				channelChangeTimeStamp
					DisplayString,
				currentChanNum
					Unsigned32,
				currentChanScore
					Unsigned32,
				dstChanNum
					Unsigned32,
				dstChanScore
					Unsigned32
			 }

		-- 1.3.6.1.4.1.17270.44.1.2.9.1.1
		radioIndex OBJECT-TYPE
			SYNTAX Unsigned32 (1..4294967295)
			MAX-ACCESS not-accessible
			STATUS current
			DESCRIPTION
				"Row entry index for the radio band"
			::= { radioTrigEvEntry 1 }

		
		-- 1.3.6.1.4.1.17270.44.1.2.9.1.2
		channelChangeTimeStamp OBJECT-TYPE
			SYNTAX DisplayString
			MAX-ACCESS read-only
			STATUS current
			DESCRIPTION
				"Time stamp for the channel change trigger event"
			::= { radioTrigEvEntry 2 }

		
		-- 1.3.6.1.4.1.17270.44.1.2.9.1.3
		currentChanNum OBJECT-TYPE
			SYNTAX Unsigned32
			MAX-ACCESS read-write
			STATUS current
			DESCRIPTION
				"current operational channel"
			::= { radioTrigEvEntry 3 }

		
		-- 1.3.6.1.4.1.17270.44.1.2.9.1.4
		currentChanScore OBJECT-TYPE
			SYNTAX Unsigned32
			MAX-ACCESS read-write
			STATUS current
			DESCRIPTION
				"current channel's score"
			::= { radioTrigEvEntry 4 }

		
		-- 1.3.6.1.4.1.17270.44.1.2.9.1.5
		dstChanNum OBJECT-TYPE
			SYNTAX Unsigned32
			MAX-ACCESS read-write
			STATUS current
			DESCRIPTION
				"Target destination channel number"
			::= { radioTrigEvEntry 5 }

		
		-- 1.3.6.1.4.1.17270.44.1.2.9.1.6
		dstChanScore OBJECT-TYPE
			SYNTAX Unsigned32
			MAX-ACCESS read-write
			STATUS current
			DESCRIPTION
				"Target destination channel score"
			::= { radioTrigEvEntry 6 }

		
		-- 1.3.6.1.4.1.17270.44.1.2.10
		droppedClientTable OBJECT-TYPE
			SYNTAX SEQUENCE OF DroppedClientEntry
			MAX-ACCESS not-accessible
			STATUS current
			DESCRIPTION
				"Table containing the list of clients that did not make the channel change"
			::= { dcs 10 }

		
		-- 1.3.6.1.4.1.17270.44.1.2.10.1
		droppedClientEntry OBJECT-TYPE
			SYNTAX DroppedClientEntry
			MAX-ACCESS not-accessible
			STATUS current
			DESCRIPTION
				"dropped client row entry"
			INDEX { clientIndex }
			::= { droppedClientTable 1 }

		
		DroppedClientEntry ::=
			SEQUENCE { 
				clientIndex
					Unsigned32,
				clientMACAddr
					DisplayString,
				clientRSSILevel
					Unsigned32,
				clientType
					DisplayString,
				clientOS
					DisplayString
			 }

		-- 1.3.6.1.4.1.17270.44.1.2.10.1.1
		clientIndex OBJECT-TYPE
			SYNTAX Unsigned32 (1..4294967295)
			MAX-ACCESS not-accessible
			STATUS current
			DESCRIPTION
				"Row entry index for the client"
			::= { droppedClientEntry 1 }

		
		-- 1.3.6.1.4.1.17270.44.1.2.10.1.2
		clientMACAddr OBJECT-TYPE
			SYNTAX DisplayString
			MAX-ACCESS read-only
			STATUS current
			DESCRIPTION
				"MAC address of the client that didnt make the channel change"
			::= { droppedClientEntry 2 }

		
		-- 1.3.6.1.4.1.17270.44.1.2.10.1.3
		clientRSSILevel OBJECT-TYPE
			SYNTAX Unsigned32
			MAX-ACCESS read-write
			STATUS current
			DESCRIPTION
				"RSSI level (in negative dBm) of the client that didnt make the channel change"
			::= { droppedClientEntry 3 }

		
		-- 1.3.6.1.4.1.17270.44.1.2.10.1.4
		clientType OBJECT-TYPE
			SYNTAX DisplayString
			MAX-ACCESS read-write
			STATUS current
			DESCRIPTION
				"Type of client - Dell laptop, iPhone, iPad etc if available"
			::= { droppedClientEntry 4 }

		
		-- 1.3.6.1.4.1.17270.44.1.2.10.1.5
		clientOS OBJECT-TYPE
			SYNTAX DisplayString
			MAX-ACCESS read-write
			STATUS current
			DESCRIPTION
				"OS of the client (IOS, Window 7, Linux, MAC OS etc) if available"
			::= { droppedClientEntry 5 }

		
-- Air Time Management feature objects
		-- 1.3.6.1.4.1.17270.44.1.3
		atm OBJECT IDENTIFIER ::= { peHSDCPEMIBObjects 3 }

		
		-- 1.3.6.1.4.1.17270.44.1.3.1
		enableATM OBJECT-TYPE
			SYNTAX TruthValue
			MAX-ACCESS read-write
			STATUS current
			DESCRIPTION
				"Flag to enable/disable Air Time Management (ATM) feature on the device. By 
				default this value is false and the feature is disabled."
			::= { atm 1 }

		
		-- 1.3.6.1.4.1.17270.44.3
		peHSDCPENotification OBJECT IDENTIFIER ::= { peHSDCPE 3 }

		
		-- 1.3.6.1.4.1.17270.44.4
		dpeHSDCPEConformance OBJECT IDENTIFIER ::= { peHSDCPE 4 }

		
		-- 1.3.6.1.4.1.17270.44.4.1
		peHSDCPEGroups OBJECT IDENTIFIER ::= { dpeHSDCPEConformance 1 }

		
		-- 1.3.6.1.4.1.17270.44.4.1.1
		selfHealGroup OBJECT-GROUP
			OBJECTS { enableSelfHeal, maxSubsystemResetCount, minNumPingServer, pingInterval, numPingsPerServer, 
				pingRespWaitTime, ipv4PingServerURI, ipv6PingServerURI, resourceUsageComputeWindow, avgCPUThreshold, 
				avgMemoryThreshold, maxRebootCount }
			STATUS current
			DESCRIPTION 
				"A collection of objects that support HSD device features"
			::= { peHSDCPEGroups 1 }

		
		-- 1.3.6.1.4.1.17270.44.4.1.2
		dcsGroup OBJECT-GROUP
			OBJECTS { enableDCS, channelNum24G, channelNum5G, preferred5GChanBw, scanDwellTime, 
				maxScanSamples, channelScore5G, dstChanScore, dstChanNum, currentChanScore, 
				currentChanNum, channelChangeTimeStamp, clientType, clientRSSILevel, clientMACAddr, 
				chanScoreEvalMinInterval, clientOS, chanScoreDiffThreshold, channelScore24G }
			STATUS current
			DESCRIPTION 
				"Description."
			::= { peHSDCPEGroups 2 }

		
		-- 1.3.6.1.4.1.17270.44.4.1.3
		atmGroup OBJECT-GROUP
			OBJECTS { enableATM }
			STATUS current
			DESCRIPTION 
				"Description."
			::= { peHSDCPEGroups 3 }

		
	
	END
-- This MIB contains the diagnostic OIDs for the High Speed Data (HSD) CPEs for PE 
-- defined features of Self-Heal, Dynamic Channel Selection (DCS), Air Time Management 
-- (ATM)

--
-- PE-HSD-CPE-MIB.mib
--
